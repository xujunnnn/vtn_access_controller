module mac_acl_sub {
    yang-version 1;
    namespace "urn:opendaylight:mac_acl";
    prefix acl;
    /* OpenDaylight MD-SAL */
    import ietf-yang-types {
        prefix yang;
        revision-date 2013-07-15;
    }
    /* OpenDaylight controller */
    import opendaylight-inventory {
        prefix inv;
        revision-date 2013-08-19;
    }
    import mac_acl_type{
    	prefix type;
    	revision-date 2017-12-12;
    }
    description
        "The module that descripes various data types used by the VTN Manager.";

      revision 2017-12-12 {
          description "Initial revision.";
      }
    
    grouping mac-acl-config {
        description
          "Describes configuration for a MAC mapping.";

        container allowed-hosts {
            description
              "A set of hosts to be mapped by MAC mapping.
               If a host in this container does not specify a MAC address,
               all the hosts detected over the specified VLAN will be mapped.
               For example, if \"@10\" is configured in this container,
               all hosts detected on VLAN 10 will be mapped.

               Note that zero, broadcast address, and multicast address
               cannot be specified as MAC address. In addition, multiple host
               information with the same MAC address cannot be configured in
               this set.";
            uses type:vlan-host-desc-set;
        }

        container denied-hosts {
            description
              "A set of hosts not to be mapped by MAC mapping.
               This container is used to exclude specific hosts from mapping
               when host information in `allowed-hosts' does not specify any
               MAC address. Unlike `allowed-hosts', every hosts in this
               container must specify a MAC address.

               The hosts in this container is evaluated before
               `allowed-hosts'. If the same host information is specified in
               both `allowed-hosts' and this container, that host will not be
               mapped by this MAC mapping.

               Note that zero, broadcast address, and multicast address
               cannot be specified as MAC address.";
            uses type:vlan-host-desc-set;
        }
    }
    
    grouping mac-acl-status {
        description
          "Describes runtime status information about MAC mapping.";
        leaf vgroup{
        	type string;
        }

        list mapped-host {
            description
              "A list of MAC addresses actually mapped to the vBridge.";
            key "mac-address";

            leaf mac-address {
                description "MAC address actually mapped to the vBridge.";
                type yang:mac-address;
            }

            leaf port-id {
                description
                  "An identifier for a physical switch port where the
                   MAC address is detected.";
                type inv:node-connector-id;
            }
        }
    }
    

    
    
    rpc set-mac-acl {
        description
          "Configure MAC mapping in the specified vBridge.

           This operation changes the specified access control list of the
           MAC mapping.

           Upon successful completion, the result of this operation will
           be set to the `status' field in the RPC output.

           `CREATED' indicates that new MAC mapping configuration has been
           created in the specified vBridge.

           `CHANGED' indicates that existing MAC mapping configuration has
           been changed.

           `REMOVED' indicates that MAC mapping configuration has been removed
           from the specified vBridge.

           Null indicates that MAC mapping configuration in the specified
           vBridge was not changed.

           On failure, one of vtn-error-tag value which indicates the cause
           of error is set into application tag in RPC error.

           `BADREQUEST' is set if the RPC input contains invalid data.

           `NOTFOUND' is set if the VTN specified by `tenant-name' is not
           present.

           `NOTFOUND' is set if the vBridge specified by `tenant-name' and
           `bridge-name' is not present.

           `CONFLICT' is set if this operation tries to map a host already
           mapped by another MAC mapping.

           `CONFLICT' is set if this operation tries to add a MAC address
           into `allowed-hosts' in the MAC mapping configuration, and that
           MAC address is already configured in `allowed-hosts'.

           `INTERNALERROR' is set if the operation failed due to internal
           error.";

        input {
            /* The location of the vBridge. */
            leaf vtn{
            	type string;
            }
            leaf vgroup{
            	type string;
            }
            leaf acl-type {
                description
                  "The type of the target access control list.
                   `ALLOW' indicates that the `allowed-hosts' container in the
                   MAC mapping configuration should be modified.
                   `DENY' indicates that the `denied-hosts' container in the
                   MAC mapping configuration should be modified.

                   Null is treated as if `ALLOW' is specified.";
                type type:acl-type;
            }

            leaf operation {
                description
                  "Describes how to update the specified access control list
                   in the MAC mapping configuration.

                   If `SET' is specified, the given list of host information
                   will be applied to the specified access control list as
                   specified. In other words, the specified access control
                   list is cleared, and then the given host information will
                   be added to the specified access control list.
                   Note that MAC mapping will be removed if both
                   `allowed-hosts' and `denied-hosts' container in the MAC
                   mapping configuration become empty.

                   If `ADD' is specified, the given list of host information
                   will be added to the specified access control list in the
                   MAC mapping configuration.

                   If `REMOVE' is specified, the host information configured
                   in the RPC input will be removed from the specified access
                   conrol list in the MAC mapping configuration.
                   Note that MAC mapping will be removed if both
                   `allowed-hosts' and `denied-hosts' container in the MAC
                   mapping configuration become empty.

                   Null will be treated as if `ADD' is specified.";
                type type:update-operation-type;
            }

            leaf-list hosts {
                description
                  "A set of host information to be added to or removed from
                   the access control list in the MAC mapping configuration.
                   Duplicate hosts will be eliminated automatically.";
                type type:host-desc;
            }
        }

        output {
            uses type:rpc-result;
        }
    }

    rpc get-mac-acl {
        description
          "Get a list of hosts where mapping is actually active based on MAC
           mapping configured in the specified vBridge.

           Upon successful completion, a list of host information is will be
           set to the RPC output.

           On failure, one of vtn-error-tag value which indicates the cause
           of error is set into application tag in RPC error.

           `BADREQUEST' is set if the RPC input contains invalid data.

           `NOTFOUND' is set if the VTN specified by `tenant-name' is not
           present.

           `NOTFOUND' is set if the vBridge specified by `tenant-name' and
           `bridge-name' is not present.

           `INTERNALERROR' is set if the operation failed due to internal
           error.";

        input {
            /* The location of the vBridge. */
        	  leaf vtn{
              	type string;
              }
              leaf vgroup{
              	type string;
              }
          
	
            leaf-list mac-addresses {
                description
                  "A list of MAC addresses to be searched.
                   If this field is omitted or an empty list is specified,
                   all the host information mapped to the specified vBridge by
                   the MAC mapping will be set to the RPC output.
                   Duplicates in this list will be eliminated automatically.";
                type yang:mac-address;
            }
        }

        output {
            leaf configured {
                description
                  "True is set only if the MAC mapping is configured in the
                   vBridge specified by the RPC input.";
                type boolean;
            }

            list mac-mapped-host {
                description
                  "A list of host information mapped to the specified vBridge
                   by MAC mapping.";
                uses mac-acl-status;
            }
        }
    }
    
    
}
